import json
import math
import os
from pathlib import Path
import traceback

import FreeCAD as App
import FreeCADGui as Gui
import Part
import Sketcher


OUTPUT = Path(os.environ["CAD_AGENT_OUTPUT"])
MODEL = json.loads(Path(os.environ["CAD_AGENT_MODEL"]).read_text(encoding="utf-8"))
EDIT = json.loads(Path(os.environ["CAD_AGENT_EDIT"]).read_text(encoding="utf-8")) if os.environ.get("CAD_AGENT_EDIT") else None
PREEXISTING = set(App.listDocuments())


def inspect(document):
    expected = {}
    for entity in MODEL["entities"]:
        expected[entity["component"]] = expected.get(entity["component"], 0) + 1
    sketches = {obj.Name: obj for obj in document.Objects if obj.TypeId == "Sketcher::SketchObject"}
    if set(sketches) != set(expected):
        raise RuntimeError("Native component sketches differ from compiled model.")
    for name, count in expected.items():
        if len(sketches[name].Geometry) != count:
            raise RuntimeError("Native geometry count differs: " + name)
    checks = []
    for entity in MODEL["entities"]:
        sketch = document.getObject(entity["component"])
        geometry = sketch.Geometry[entity["geometry_index"]]
        if sketch.solve() != 0:
            raise RuntimeError("Sketch solver conflict: " + sketch.Name)
        shape = geometry.toShape()
        if not shape.isValid():
            raise RuntimeError("Invalid native geometry.")
        if entity["type"] == "line":
            if geometry.StartPoint.distanceToPoint(App.Vector(*entity["start"], 0)) > 1e-6 or geometry.EndPoint.distanceToPoint(App.Vector(*entity["end"], 0)) > 1e-6:
                raise RuntimeError("Line coordinates differ after solving/reopening.")
        elif entity["type"] == "circle":
            if abs(geometry.Radius - entity["radius"]) > 1e-6 or geometry.Center.distanceToPoint(App.Vector(*entity["center"], 0)) > 1e-6:
                raise RuntimeError("Circle dimensions differ.")
        else:
            for point in entity["fit_points"]:
                if shape.distToShape(Part.Vertex(App.Vector(*point, 0)))[0] > 1e-5:
                    raise RuntimeError("Spline fit point not represented by native curve.")
        checks.append({"id": entity["id"], "type": entity["type"], "length": shape.Length, "valid": True})
    return checks


def new_sketch(document, name, meaning):
    sketch = document.addObject("Sketcher::SketchObject", name)
    if sketch.Name != name:
        raise RuntimeError("Component name unavailable in native document: " + name)
    sketch.Label = meaning
    sketch.ViewObject.LineColor = (0.0, 0.0, 0.0)
    sketch.ViewObject.PointSize = 1
    sketch.ViewObject.LineWidth = 2
    return sketch


def add_entity(sketch, entity):
    if entity["type"] == "line":
        geometry = Part.LineSegment(App.Vector(*entity["start"], 0), App.Vector(*entity["end"], 0))
    elif entity["type"] == "circle":
        geometry = Part.Circle(App.Vector(*entity["center"], 0), App.Vector(0, 0, 1), entity["radius"])
    else:
        geometry = Part.BSplineCurve()
        geometry.interpolate([App.Vector(*point, 0) for point in entity["fit_points"]])
    index = sketch.addGeometry(geometry, False)
    if index != entity["geometry_index"]:
        raise RuntimeError("Geometry index differs from compiled component model.")
    if entity["type"] == "line":
        if abs(entity["start"][1] - entity["end"][1]) < 1e-9:
            sketch.addConstraint(Sketcher.Constraint("Horizontal", index))
        elif abs(entity["start"][0] - entity["end"][0]) < 1e-9:
            sketch.addConstraint(Sketcher.Constraint("Vertical", index))
    elif entity["type"] == "circle":
        sketch.addConstraint(Sketcher.Constraint("Radius", index, entity["radius"]))


def fingerprint(sketch):
    geometry = []
    for item in sketch.Geometry:
        shape = item.toShape()
        box = shape.BoundBox
        geometry.append([type(item).__name__, round(shape.Length, 9), [round(value, 9) for value in (box.XMin, box.YMin, box.XMax, box.YMax)]])
    return {"label": sketch.Label, "constraints": sketch.ConstraintCount, "geometry": geometry}


def apply_edit(document):
    for operation in EDIT["operations"]:
        name = operation["component"]
        sketch = document.getObject(name)
        if operation["op"] == "add":
            if sketch is not None:
                raise RuntimeError("Added component already exists in base document: " + name)
            sketch = new_sketch(document, name, operation["meaning"])
        elif sketch is None or sketch.TypeId != "Sketcher::SketchObject":
            raise RuntimeError("Base document lacks component sketch: " + name)
        if operation["op"] == "remove":
            document.removeObject(name)
            continue
        if operation["op"] == "replace":
            sketch.deleteAllConstraints()
            sketch.deleteAllGeometry()
            if sketch.Geometry or sketch.ConstraintCount:
                raise RuntimeError("Replaced component was not cleared: " + name)
            sketch.Label = operation["meaning"]
        for entity in operation["entities"]:
            add_entity(sketch, entity)


try:
    edit_report = None
    if EDIT:
        document = App.openDocument(EDIT["base_native"])
        preserved = {name: fingerprint(document.getObject(name)) for name in EDIT["preserved"]}
        apply_edit(document)
    else:
        document = App.newDocument("AgentDraft")
        for entity in MODEL["entities"]:
            name = entity["component"]
            sketch = document.getObject(name)
            if sketch is None:
                sketch = new_sketch(document, name, MODEL["component_meanings"][name])
            add_entity(sketch, entity)
    document.recompute()
    inspect(document)
    document.saveAs(str(OUTPUT / "draft.FCStd"))
    App.closeDocument(document.Name)
    reopened = App.openDocument(str(OUTPUT / "draft.FCStd"))
    reopened.recompute()
    checks = inspect(reopened)
    if EDIT:
        if any(fingerprint(reopened.getObject(name)) != value for name, value in preserved.items()):
            raise RuntimeError("Preserved component changed during native edit.")
        edit_report = {"base_native": EDIT["base_native"], "base_attempt": EDIT.get("base_attempt"),
                       "operations": [{"op": item["op"], "component": item["component"], "entities": len(item.get("entities", []))} for item in EDIT["operations"]],
                       "preserved_components": sorted(preserved), "preserved_verified": True,
                       "evidence": "Preserved sketches compared before edit and after save/reopen: label, constraint count, geometry type, length and bounds."}
    Gui.activeDocument().activeView().viewTop()
    Gui.activeDocument().activeView().fitAll()
    Gui.updateGui()
    Gui.activeDocument().activeView().saveImage(str(OUTPUT / "preview.png"), 1400, 900, "White")
    report = {"status": "passed", "reopened": True, "entities": checks, "components": len(reopened.Objects),
              "constraints": sum(obj.ConstraintCount for obj in reopened.Objects),
              "fully_constrained_components": sum(obj.FullyConstrained for obj in reopened.Objects),
              "policy": "Component sketches with native H/V and radius constraints; free DOFs retained, not falsely fixed.",
              "review_status": "needs_review"}
    if edit_report:
        report["edit"] = edit_report
except Exception as error:
    report = {"status": "failed", "error": str(error), "traceback": traceback.format_exc()}
finally:
    for name in set(App.listDocuments()) - PREEXISTING:
        App.closeDocument(name)
(OUTPUT / "geometry.json").write_text(json.dumps(report, indent=2) + "\n", encoding="utf-8")
if os.environ.get("CAD_AGENT_DIRECT") == "1":
    from PySide import QtCore, QtWidgets
    QtCore.QTimer.singleShot(0, QtWidgets.QApplication.quit)
